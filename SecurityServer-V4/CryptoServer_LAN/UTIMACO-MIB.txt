UTIMACO-MIB DEFINITIONS ::= BEGIN

--
-- Top-level infrastructure of the Utimaco MIB tree
--

IMPORTS
    MODULE-IDENTITY, enterprises FROM SNMPv2-SMI;

utimaco MODULE-IDENTITY
    LAST-UPDATED "201507090000Z"  -- July 09, 2015
    ORGANIZATION 
        "Utimaco IS GmbH
        http://www.utimaco.com"
    CONTACT-INFO    
        "Utimaco HSM:
            email: hsm@utimaco.com
        Utimaco LIMS:
            email: li-contact@utimaco.com"
    DESCRIPTION
        "Top-level infrastructure of the Utimaco MIB tree"
    
    REVISION     "201211300000Z"  -- November 30, 2012
    DESCRIPTION
        "Changed organization and contact information"
    REVISION     "201201170000Z"  -- January 17, 2012
    DESCRIPTION
        "Initial Version"
    ::= { enterprises 3159}						  

END
